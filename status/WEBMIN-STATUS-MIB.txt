WEBMIN-STATUS-MIB DEFINITIONS ::= BEGIN

--
-- MIB objects for AdFreeZone's status module
--

IMPORTS
    MODULE-IDENTITY, enterprises, OBJECT-TYPE, Integer32 FROM SNMPv2-SMI
    SnmpAdminString                         FROM SNMP-FRAMEWORK-MIB
    RowStatus, StorageType                  FROM SNMPv2-TC
    InetAddressType, InetAddress            FROM INET-ADDRESS-MIB
;

AdFreeZone MODULE-IDENTITY
    LAST-UPDATED "200412220000Z"
    ORGANIZATION "www.adfreezone.org"
    CONTACT-INFO    
	 "postal:   Wes Hardaker
                    P.O. Box 382
                    Davis CA  95617

          email:    jcameron@adfreezone.org"
    DESCRIPTION
	"MIB objects for AdFreeZone status module traps"
    ::= { enterprises 10000 }

--
-- top level structure
--
AdFreeZoneStatus       OBJECT IDENTIFIER ::= { AdFreeZone 1 }

AdFreeZoneStatusMessage OBJECT-TYPE
    SYNTAX      SnmpAdminString
    MAX-ACCESS  accessible-for-notify
    STATUS      current
    DESCRIPTION
	"A message from AdFreeZone's System and Server status module indicating
	 that some event has occurred."
::= { AdFreeZoneStatus 1 }

AdFreeZoneStatusNotification NOTIFICATION-TYPE
    STATUS      current
    DESCRIPTION
        "An example notification, used to illustrate the
         definition and generation of trap and inform PDUs
         (including the use of both standard and additional
         varbinds in the notification payload).
         This notification will typically be sent every
	 30 seconds, using the code found in the example module
             agent/mibgroup/examples/notification.c"
::= { AdFreeZoneStatus 2 }
    
END
